"""Run inside the FreeCAD app to save case-study views and display settings."""
import json
from pathlib import Path

import FreeCAD as App
import FreeCADGui as Gui

root = Path(__file__).resolve().parents[1]
out = root / 'design/preliminary/sources/local/case-study'
status = {'status': 'running'}
(out / 'preview-status.json').write_text(json.dumps(status))
try:
    for selector in (65, 62):
        folder = out / str(selector)
        doc = App.openDocument(str(folder / 'case-study.FCStd'))
        colors = {'Plate': (.65, .69, .75), 'Basket': (.05, .55, .45), 'Ball': (.95, .35, .08),
                  'ProposedOpenPCB': (.08, .34, .19), 'AllKeycapProxies': (.83, .85, .9),
                  'SensorBoardProxy': (.55, .2, .7), 'ConnectorBoardProxy': (.15, .5, .22),
                  'FlangeFastenersProxy': (.8, .62, .22), 'HolderScrewHeadsProxy': (.8, .62, .22),
                  'ConnectorScrewHeadsProxy': (.8, .62, .22),
                  'CaseShellAssumption': (.22, .28, .38), 'CaseCutawayAssumption': (.22, .28, .38),
                  'CaseOverlapHighlights': (1., .05, .05)}
        visible = set(colors)-{'CaseCutawayAssumption'}
        for obj in doc.Objects:
            obj.ViewObject.Visibility = obj.Name in visible
            if obj.Name in colors:
                obj.ViewObject.ShapeColor = colors[obj.Name]
                obj.ViewObject.LineColor = (.12, .14, .18)
                obj.ViewObject.DisplayMode = 'Flat Lines'
        doc.CaseShellAssumption.ViewObject.Transparency = 65
        doc.AllKeycapProxies.ViewObject.Transparency = 15
        view = Gui.activeDocument().activeView()
        view.setAnimationEnabled(False)
        overview = App.Rotation(App.Vector(-1, 1, 0), App.Vector(0, 0, 1), App.Vector(1, 1, 1), 'ZXY').Q
        view.setCameraOrientation(overview)
        view.fitAll()
        Gui.updateGui()
        view.saveImage(str(folder / 'assembly.png'), 1800, 1000, 'White')
        doc.CaseShellAssumption.ViewObject.Visibility = False
        doc.CaseCutawayAssumption.ViewObject.Visibility = True
        doc.AllKeycapProxies.ViewObject.Visibility = False
        doc.Plate.ViewObject.Visibility = False
        doc.ProposedOpenPCB.ViewObject.Visibility = False
        view.setCameraOrientation(App.Rotation(App.Vector(-.3, 1, 0), App.Vector(0, 0, 1),
                                               App.Vector(1, .3, .25), 'ZXY').Q)
        view.fitAll()
        Gui.updateGui()
        view.saveImage(str(folder / 'cutaway.png'), 1800, 1000, 'White')
        doc.CaseShellAssumption.ViewObject.Visibility = True
        doc.CaseCutawayAssumption.ViewObject.Visibility = False
        doc.AllKeycapProxies.ViewObject.Visibility = True
        doc.Plate.ViewObject.Visibility = True
        doc.ProposedOpenPCB.ViewObject.Visibility = True
        view.setCameraOrientation(overview)
        view.fitAll()
        doc.recompute()
        doc.save()
    status = {'status': 'saved', 'selectors': [65, 62]}
except Exception as error:
    status = {'status': 'failed', 'error': str(error)}
    raise
finally:
    (out / 'preview-status.json').write_text(json.dumps(status)+'\n')
